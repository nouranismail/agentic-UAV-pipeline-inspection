# uav_mission_supervisor_requirements

## UAV-MSN-REQ-001: Upon initialization, the mission supervisor shall initialize its active mode and missionMode output to NormalInspection. (Functional)
Acceptance criteria: With valid healthy battery and routeComplete=false, the first execution reports NormalInspection. A safety condition present on the first execution shall still be processed by the priority logic.
- Rationale: Provides a defined startup state without expanding the demonstration with a mission-start mode.
- Keywords: draft, uav-mission-supervisor

## UAV-MSN-REQ-002: While the supervisor is in NormalInspection, if batteryPercent is valid and greater than Battery_Threshold_Low (25%) and routeComplete is false, the supervisor shall remain in NormalInspection. (Functional)
Acceptance criteria: For any finite battery value in (25,100] with routeComplete=false, the state and output remain NormalInspection.
- Rationale: Defines nominal inspection behavior.
- Keywords: draft, uav-mission-supervisor

## UAV-MSN-REQ-003: While the supervisor is not in a terminal state, when batteryPercent is greater than Battery_Threshold_Critical (10%) and less than or equal to Battery_Threshold_Low (25%), the supervisor shall enter or remain in ReturnToHome. (Functional)
Acceptance criteria: Values of exactly 25% and strictly between 10% and 25% produce ReturnToHome by the end of the execution step.
- Rationale: Initiates the committed low-battery safety response, including the 25% boundary.
- Keywords: draft, uav-mission-supervisor

## UAV-MSN-REQ-004: While the supervisor is not in a terminal state, when batteryPercent is less than or equal to Battery_Threshold_Critical (10%), the supervisor shall enter or remain in SafeLanding. (Functional)
Acceptance criteria: Exactly 10% and all valid values below 10% produce SafeLanding by the end of the execution step.
- Rationale: Critical battery requires the highest-priority safe response, including the 10% boundary.
- Keywords: draft, uav-mission-supervisor

## UAV-MSN-REQ-005: When batteryPercent is less than or equal to Battery_Threshold_Critical (10%), the supervisor shall select SafeLanding and shall not select ReturnToHome, even though the value is also below the low-battery threshold. (Functional)
Acceptance criteria: At 10% and below, the observed state/output is exclusively SafeLanding.
- Rationale: Removes overlapping-guard ambiguity and establishes critical-over-low priority.
- Keywords: draft, uav-mission-supervisor

## UAV-MSN-REQ-006: When routeComplete is true and coincides with a low, critical, or invalid battery condition, the supervisor shall select the applicable battery safety response instead of MissionComplete. (Functional)
Acceptance criteria: Low battery plus route completion produces ReturnToHome; critical or invalid battery plus route completion produces SafeLanding.
- Rationale: Safety behavior must override routine mission completion.
- Keywords: draft, uav-mission-supervisor

## UAV-MSN-REQ-007: While the supervisor is in NormalInspection, when routeComplete is true and batteryPercent is valid and greater than Battery_Threshold_Low (25%), the supervisor shall enter MissionComplete. (Functional)
Acceptance criteria: A healthy battery with routeComplete=true produces MissionComplete by the end of the execution step.
- Rationale: Completes the mission when no battery safety response has priority.
- Keywords: draft, uav-mission-supervisor

## UAV-MSN-REQ-008: Once the supervisor enters SafeLanding, it shall remain in SafeLanding for all subsequent input values. (Functional)
Acceptance criteria: No later healthy, low, critical, invalid, or route-complete input causes an exit; missionMode remains SafeLanding.
- Rationale: Safe landing is an approved terminal safety state.
- Keywords: draft, uav-mission-supervisor

## UAV-MSN-REQ-009: Once the supervisor enters MissionComplete, it shall remain in MissionComplete for all subsequent input values. (Functional)
Acceptance criteria: No later input causes an exit; missionMode remains MissionComplete.
- Rationale: Mission Complete is an approved terminal state.
- Keywords: draft, uav-mission-supervisor

## UAV-MSN-REQ-010: Once the supervisor enters ReturnToHome, it shall not return to NormalInspection or transition to MissionComplete; it shall remain in ReturnToHome unless a critical or invalid battery input requires escalation to SafeLanding. (Functional)
Acceptance criteria: Battery recovery and routeComplete do not release ReturnToHome; a later critical or invalid battery value changes the state only to SafeLanding.
- Rationale: Treats return-to-home as committed while preserving escalation to the higher-priority safe state.
- Keywords: draft, uav-mission-supervisor

## UAV-MSN-REQ-011: If batteryPercent is non-finite, below 0%, or above 100%, then the supervisor shall enter SafeLanding, unless it is already in another approved terminal state. (Functional)
Acceptance criteria: Negative, above-range, NaN, +Inf, and -Inf inputs produce SafeLanding from a nonterminal state.
- Rationale: Implements the repository-required fail-safe response for invalid input.
- Keywords: draft, uav-mission-supervisor

## UAV-MSN-REQ-012: For every active state and input combination, the mission supervisor shall produce exactly one deterministic next state and a missionMode value corresponding to that state. (Functional)
Acceptance criteria: Repeated executions from the same state with identical inputs produce identical state/output results; every output is one valid MissionMode member.
- Rationale: Prevents ambiguous simultaneous transitions and stale or contradictory outputs.
- Keywords: draft, uav-mission-supervisor
